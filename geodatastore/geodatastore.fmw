FME workspace geodatastore.fmw

Parameters:
- Geodatastore_Username =
- Geodatastore_Password =
- Dataset_Title =
- Dataset_Filename =   # *.* Dataset_Filename
- Thumbnail_Filename =   # *.* Thumbnail_Filename
- Publish = true

Creator
    GEOMTYPE = Geometry Object
    NUM = 1
    CREATED -> GeoDS_List
GeoDS_List: HTTPCaller
    AUTH_METHOD = Basic
    TARGET_ATTR = _response_body
    TARGET_ATTR_ENCODING = auto-detect
    HTTP_METHOD = POST
    MULTIPARTS = q StringUpload SOURCE_EXPRESSION;*$(Dataset_Title)*;MIME_TYPE;text/plain;FME_CONTROLLER_QUERY_FILE;transformers\dependencies\http\StringUpload.fme pageSize StringUpload SOURCE_EXPRESSION;100;MIME_TYPE;text/plain;FME_CONTROLLER_QUERY_FILE;transformers\dependencies\http\StringUpload.fme status StringUpload SOURCE_EXPRESSION;published;MIME_TYPE;text/plain;FME_CONTROLLER_QUERY_FILE;transformers\dependencies\http\StringUpload.fme
    CONNECTION_TIMEOUT_LENGTH = 60
    STATUS_CODE_ATTR = _http_status_code
    USE_COOKIES = No
    TARGET_URL = https://geodatastore.pdok.nl/api/v1/datasets
    TRANSFER_TIMEOUT_LENGTH = 90
    UPLOAD_TYPE = Multipart / Form Data
    AUTH_PASSWORD = $(Geodatastore_Password)
    AUTH_USERNAME = $(Geodatastore_Username)
    SAVE_FILE = Attribute
    FOLLOW_REDIRECTS = Yes
    ERROR_ATTR = _error
    VERIFY_SSL_CERTIFICATES = Yes
    RESPONSE_HEADER_LIST_ATTR = _headers
    -> JSONFragmenter
JSONFragmenter
    JSON_ATTR = _response_body
    JSON_QUERY = json["metadata"][*]
    EXTRACT_ATTR = Yes
    RECURSIVE = Yes
    EXPLODE_FORMAT = JSON
    NEW_ATTRIBUTES = title identifier
    EXPLODED -> TestFilter
TestFilter
    DEFAULT_VALUE = <UNFILTERED>
    TEST_LIST = BOOL_OP,OR,COMPOSITE_TEST,<Unused>,TEST_CLAUSE,"TEST @Value(title) = $(Dataset_Title)",Match
    Match -> GeoDS_Update
GeoDS_Update: HTTPCaller
    AUTH_METHOD = Basic
    TARGET_ATTR = _response_body
    TARGET_ATTR_ENCODING = auto-detect
    HTTP_METHOD = POST
    MULTIPARTS:
      publish StringUpload SOURCE_EXPRESSION;$(Publish);MIME_TYPE;text/plain;FME_CONTROLLER_QUERY_FILE;transformers\dependencies\http\StringUpload.fme dataset FileUpload SOURCE_FILE;$(Dataset_Filename);MIME_TYPE;application/octet-stream;FME_CONTROLLER_QUERY_FILE;transformers\dependencies\http\FileUpload.fme thumbnail FileUpload SOURCE_FILE;$(Thumbnail_Filename);MIME_TYPE;application/octet-stream;FME_CONTROLLER_QUERY_FILE;transformers\dependencies\http\FileUpload.fme metadata StringUpload SOURCE_EXPRESSION;{
         "title": "$(Dataset_Title)"
      };MIME_TYPE;text/plain;FME_CONTROLLER_QUERY_FILE;transformers\dependencies\http\StringUpload.fme
    CONNECTION_TIMEOUT_LENGTH = 60
    STATUS_CODE_ATTR = _http_status_code
    USE_COOKIES = No
    TARGET_URL = https://geodatastore.pdok.nl/api/v1/dataset/@Value(identifier)
    TRANSFER_TIMEOUT_LENGTH = 90
    UPLOAD_TYPE = Multipart / Form Data
    AUTH_PASSWORD = $(Geodatastore_Password)
    AUTH_USERNAME = $(Geodatastore_Username)
    SAVE_FILE = Attribute
    FOLLOW_REDIRECTS = Yes
    ERROR_ATTR = _error
    VERIFY_SSL_CERTIFICATES = Yes
    RESPONSE_HEADER_LIST_ATTR = _headers
    -> GeoDS_List_Output
    <Rejected> -> GeoDS_Update__Rejected_
GeoDS_List_Output: Inspector
GeoDS_Update__Rejected_: Inspector

Bookmark: Json van de datasets
Note: Haal alle datasets die voldoen aan het filter $(Dataset_Title)

Bookmark: Lijst met datasets
Note: Json naar features
