FME workspace ngr-metadata.fmw

Parameters:
- organisatie = Provincie Groningen   # Organisatie
- max_records = 1000   # Maximum aantal records
- output_file =   # Excel-bestand voor uitvoer

Writers:
- XLSXW_1: XLSXW to $(output_file)

Note: Auteur: Willy Tadema / Datum: 20 juli 2018 / Omschrijving: / Workspace om te demonstreren hoe je de metadata kunt opvragen die door de provincie Groningen in het Nationaal Georegister gepubliceerd is. / Published parameters: / organisatie - organisatie waarvan de metadata opgevraagd moet worden (default: Provincie Groningen) / max_records - het maximum aantal records dat de API per request retourneert (default: 1000) / output_file - het uitvoerbestand in Excel

Bookmark: Data inlezen
  NGR API bevragen en JSON response klaarzetten voor verdere verwerking.
Creator
    GEOMTYPE = Geometry Object
    NUM = 1
    CREATED -> HTTPCaller
HTTPCaller
    TARGET_URL = https://nationaalgeoregister.nl/geonetwork/srv/dut/q?
    VERIFY_SSL_CERTIFICATES = Yes
    FOLLOW_REDIRECTS = Yes
    ERROR_ATTR = _error
    TARGET_ATTR = _response_body
    ADDITIONAL_URL_PARAMETERS = _content_type;json bucket;s101 facet.q; fast;index from;1 to;$(max_records) isChild;'false' orgName;$(organisatie) resultType;details sortBy;relevance
    STATUS_CODE_ATTR = _http_status_code
    SAVE_FILE = Attribute
    RESPONSE_HEADER_LIST_ATTR = _headers
    HTTP_METHOD = GET
    USE_COOKIES = No
    CONNECTION_TIMEOUT_LENGTH = 60
    TRANSFER_TIMEOUT_LENGTH = 90
    TARGET_ATTR_ENCODING = auto-detect
    -> JSONFragmenter
JSONFragmenter
    EXPLODE_FORMAT = JSON
    EXTRACT_ATTR = Yes
    JSON_QUERY = json["metadata"][*]
    JSON_ATTR = _response_body
    RECURSIVE = Yes
    FRAGMENTS -> AttributeExposer
AttributeExposer
    ATTR_LIST = abstract,defaultTitle,conditionApplyingToAccessAndUse{},keyword{},license,lineage,link{},protocol{},responsibleParty{},revisionDate,status,title,topicCat{},type,updateFrequency,useLimitation
    -> ListConcatenator

Bookmark: Lijsten 'platslaan'
ListConcatenator
    LIST_ATTR = keyword{}
    SEP = ,
    DROP_EMPTY_PARTS = Yes
    VAL_ATTR = keywords
    -> ListConcatenator_2
ListConcatenator_2
    LIST_ATTR = topicCat{}
    SEP = ,
    DROP_EMPTY_PARTS = Yes
    VAL_ATTR = topicCats
    -> AttributeCreator

Bookmark: WFS en WMS endpoint bepalen
  URL en laagnaam
AttributeCreator
    ATTR_TABLE:
      SET_TO wfs = FME_CONDITIONAL:DEFAULT_VALUE'_FME_NO_OP_'BOOL_OP;OR;COMPOSITE_TEST;<Unused>;TEST @Value(link{0}) LIKE %|OGC:WFS|%'@Value(link{0})'BOOL_OP;OR;COMPOSITE_TEST;<Unused>;TEST @Value(link{1}) LIKE %|OGC:WFS|%'@Value(link{1})'BOOL_OP;OR;COMPOSITE_TEST;<Unused>;TEST @Value(link{2}) LIKE %|OGC:WFS|%'@Value(link{2})'FME_NUM_CONDITIONS4___
      SET_TO wms = FME_CONDITIONAL:DEFAULT_VALUE'_FME_NO_OP_'BOOL_OP;OR;COMPOSITE_TEST;<Unused>;TEST @Value(link{0}) LIKE %|OGC:WMS|%'@Value(link{0})'BOOL_OP;OR;COMPOSITE_TEST;<Unused>;TEST @UpperCase(@Value(link{1})) LIKE %|OGC:WMS|%'@Value(link{1})'BOOL_OP;OR;COMPOSITE_TEST;<Unused>;TEST @UpperCase(@Value(link{2})) LIKE %|OGC:WMS|%'@Value(link{2})'FME_NUM_CONDITIONS4___
    -> AttributeSplitter
AttributeSplitter
    LIST_NAME = wfs_list
    ATTR_NAME = wfs
    DROP_EMPTY_PARTS = No
    DELIMITER = |
    TRIM_OPTION = Both
    -> AttributeSplitter_2
AttributeSplitter_2
    LIST_NAME = wms_list
    ATTR_NAME = wms
    DROP_EMPTY_PARTS = No
    DELIMITER = |
    TRIM_OPTION = Both
    -> AttributeCreator_2
AttributeCreator_2
    ATTR_TABLE:
      SET_TO wfs = FME_CONDITIONAL:DEFAULT_VALUE'_FME_NO_OP_'BOOL_OP;OR;COMPOSITE_TEST;<Unused>;TEST @Value(wfs_list{2}) ATTRIBUTE_HAS_VALUE _FME_BLANK_STRING_'@Value(wfs_list{2})?service=wfs&request=GetCapabilities'FME_NUM_CONDITIONS2___
      SET_TO wfsLayer = FME_CONDITIONAL:DEFAULT_VALUE'_FME_NO_OP_'BOOL_OP;OR;COMPOSITE_TEST;<Unused>;TEST @Value(wfs_list{0}) ATTRIBUTE_HAS_VALUE _FME_BLANK_STRING_'@Value(wfs_list{0})'FME_NUM_CONDITIONS2___
      SET_TO wms = FME_CONDITIONAL:DEFAULT_VALUE'_FME_NO_OP_'BOOL_OP;OR;COMPOSITE_TEST;<Unused>;TEST @Value(wms_list{2}) ATTRIBUTE_HAS_VALUE _FME_BLANK_STRING_'@Value(wms_list{2})?service=wms&request=GetCapabilities'FME_NUM_CONDITIONS2___
      SET_TO wmsLayer = FME_CONDITIONAL:DEFAULT_VALUE'_FME_NO_OP_'BOOL_OP;OR;COMPOSITE_TEST;<Unused>;TEST @Value(wms_list{2}) ATTRIBUTE_HAS_VALUE _FME_BLANK_STRING_'@Value(wms_list{0})'FME_NUM_CONDITIONS2___
    -> NGR (writer XLSXW_1)

Bookmark: Resultaat wegschrijven naar Excel
NGR (writer XLSXW_1)
    attributes: title auto(20), defaultTitle auto(20), abstract auto(20), license auto(20), lineage auto(20), revisionDate auto(20), status auto(20), type auto(20), updateFrequency auto(20), useLimitation auto(20), keywords auto(20), topicCats auto(20), wfs auto(20), wfsLayer auto(20), wms auto(20), wmsLayer auto(20)
