FME workspace haltescan.fmw

Parameters:
- username =
- password =
- output_file =   # Uitvoerbestand in Excel

Note: Auteur: Willy Tadema / Datum: 20 juli 2018 / Omschrijving: / Workspace om te demonstreren hoe je een exportbestand uit Haltescan kunt downloaden. / Published parameters: / username - Haltescan gebruikersnaam / password - Haltescan wachtwoord / output_file - Uitvoerbestand in Excel
Creator
    GEOMTYPE = Geometry Object
    NUM = 1
    CREATED -> HTTPCaller

Bookmark: CSRF token en cookie opvragen
Note: Save Cookies = yes
HTTPCaller
    CONNECTION_TIMEOUT_LENGTH = 60
    CUSTOM_HEADERS = Host;ovbureau.haltescan.nl Connection;keep-alive User-Agent;Mozilla/5.0 (Windows NT 6.1; Win64; x64) AppleWebKit/537.36 (KHTML, like Gecko) Chrome/66.0.3359.181 Safari/537.36 Accept;image/webp,image/apng,image/*,*/*;q=0.8 Accept-Encoding;gzip, deflate, br Accept-Language;en-US,en;q=0.9
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://ovbureau.haltescan.nl
    TRANSFER_TIMEOUT_LENGTH = 90
    USE_COOKIES = Yes
    VERIFY_SSL_CERTIFICATES = No
    -> HTMLExtractor
HTMLExtractor
    HTML_FIELD = @Value(_response_body)
    HTML_SPECIFICATION = Content
    RESULT_TYPE_NAME = FIRST_MATCH
    SEARCH_TABLE = token [name="csrf_token"] value
    Results -> AttributeKeeper
AttributeKeeper
    KEEP_ATTRS = token
    -> HTTPCaller_2

Bookmark: Inloggen
HTTPCaller_2
    CONNECTION_TIMEOUT_LENGTH = 60
    CUSTOM_HEADERS = Accept;application/json, text/javascript, */*; q=0.01 Accept-Encoding;gzip, deflate, br Accept-Language;en-US,en;q=0.9 Connection;keep-alive Content-Length;@StringLength({"username": "$(username)", "password":  "$(password)"}) Content-Type;application/x-www-form-urlencoded; charset=UTF-8 DNT;1 Host;ovbureau.haltescan.nl Origin;https://ovbureau.haltescan.nl Referer;https://ovbureau.haltescan.nl/ User-Agent;Mozilla/5.0 (Windows NT 6.1; Win64; x64) AppleWebKit/537.36 (KHTML, like Gecko) Chrome/66.0.3359.181 Safari/537.36 X-CSRF-Token;@Value(token) X-Requested-With;XMLHttpRequest
    ERROR_ATTR = _error
    FOLLOW_REDIRECTS = Yes
    HTTP_METHOD = POST
    SAVE_FILE = Attribute
    STATUS_CODE_ATTR = _http_status_code
    TARGET_ATTR = _response_body
    TARGET_ATTR_ENCODING = auto-detect
    TARGET_URL = https://ovbureau.haltescan.nl/auth/login
    TRANSFER_TIMEOUT_LENGTH = 90
    UPLOAD_BODY = {"username": "$(username)", "password":  "$(password)"}
    UPLOAD_CONTENT_TYPE = JSON (application/json)
    UPLOAD_TYPE = Specify Upload Body
    USE_COOKIES = Yes
    VERIFY_SSL_CERTIFICATES = No
    -> AttributeKeeper_2
AttributeKeeper_2
    KEEP_ATTRS = _http_status_code
    -> HTTPCaller_3

Bookmark: Excel downloaden
HTTPCaller_3
    ADDITIONAL_URL_PARAMETERS = filetype;xlsx type;basic delimiter;; from_mutation_date; location;provinceId.0 category; status;
    CONNECTION_TIMEOUT_LENGTH = 60
    ERROR_ATTR = _error
    FILE_PATH_ATTR = _response_file_path
    FOLLOW_REDIRECTS = Yes
    HTTP_METHOD = GET
    OUTPUT_FILENAME = $(output_file)
    SAVE_FILE = File
    SAVE_MULTI = No
    STATUS_CODE_ATTR = _http_status_code
    TARGET_URL = https://ovbureau.haltescan.nl/batch/quays/xlsx?
    TRANSFER_TIMEOUT_LENGTH = 90
    USE_COOKIES = Yes
    VERIFY_SSL_CERTIFICATES = No
