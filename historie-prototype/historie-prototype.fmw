FME workspace historie-prototype.fmw
Title: Historie prototype
Description: Dit is een prototype voor het opbouwen van historie in het Geomagazijn op basis van mutaties in een transactioneel systeem waarin alleen actuele gegevens opgeslagen worden.

Readers:
- GEODATABASE_SDE_1: GEODATABASE_SDE

Writers:
- GEODATABASE_SDE_3: GEODATABASE_SDE

Note: Auteur: Willy Tadema / Datum: 20 juli 2017 / Omschrijving: / Dit is een protype voor het vastleggen van historie in het Geomagazijn. Het Geomagazijn is de ESRI Enterprise Geodatabase van de provincie Groningen. Deze workspace gebouwd in FME Desktop 2016 en getest met ArcGIS 10.3.1. / In sommige situaties worden in de werkprocessen bronsystemen gebruikt die geen mutatiehistorie vastleggen, terwijl dit wel wenselijk is. In die gevallen kan deze workspace uitkomst bieden. / Alle mutaties worden bewaard. Iedere feature krijgt een DATUM_AANGEMAAKT en - indien van toepassing - een DATUM_VERVALLEN. Als een feature in het bronsysteem wordt verwijderd, blijft hij in de historie bestaan. Hij krijgt in de historie dan een DATUM_VERVALLEN. / Als een attribuut of de geometrie van een feature wordt gewijzigd, wordt de oude versie van de feature afgesloten en een nieuwe versie opgevoerd. De oude versie krijgt een DATUM_VERVALLEN die gelijk is aan de DATUM_AANGEMAAKT van de nieuwe versie.
OBJ.INCLUSIEF_HISTORIE (reader GEODATABASE_SDE_1)
    attributes: OBJECTID integer, ENTITEIT_ID integer, MUTATIE_ID integer, DATUM_AANGEMAAKT date, DATUM_VERVALLEN date, ATTRIBUUT_1 char(50), ATTRIBUUT_2 integer, ATTRIBUUT_3 date, SE_ANNO_CAD_DATA blob, SHAPE.AREA double, SHAPE.LEN double
    -> InlineQuerier [ORG]
OBJ.ALLEEN_ACTUEEL (reader GEODATABASE_SDE_1)
    attributes: OBJECTID integer, ENTITEIT_ID integer, ATTRIBUUT_1 char(50), ATTRIBUUT_2 integer, ATTRIBUUT_3 date, SE_ANNO_CAD_DATA blob, SHAPE.AREA double, SHAPE.LEN double
    -> InlineQuerier [REVISED]
OBJ.INCLUSIEF_HISTORIE (writer GEODATABASE_SDE_3)
    attributes: OBJECTID integer, ENTITEIT_ID integer, MUTATIE_ID integer, DATUM_AANGEMAAKT date, DATUM_VERVALLEN date, ATTRIBUUT_1 char(50), ATTRIBUUT_2 integer, ATTRIBUUT_3 date, SE_ANNO_CAD_DATA blob, SHAPE.AREA double, SHAPE.LEN double

Bookmark: InlineQuerier
  Maximum van MUTATIEID toevoegen als attribuut
  Historie filteren op DATUM_VERVALLEN IS NULL voor actuele data
InlineQuerier
    TABLE_DEF = ORG,ENTITEIT_ID,integer,MUTATIE_ID,integer,DATUM_VERVALLEN,text,ATTRIBUUT_1,varchar(50),ATTRIBUUT_2,integer,ATTRIBUUT_3,text,REVISED,ENTITEIT_ID,integer,ATTRIBUUT_1,varchar(50),ATTRIBUUT_2,integer,ATTRIBUUT_3,text
    QUERY_SCHEMA = LATEST_VERSION,ENTITEIT_ID,integer,MUTATIE_ID,integer,ATTRIBUUT_1,varchar(50),ATTRIBUUT_2,integer,ATTRIBUUT_3,text,ORG.fme_feature_content,fme_feature_content,OrigFlag,,REVISED,ENTITEIT_ID,integer,ATTRIBUUT_1,varchar(50),ATTRIBUUT_2,integer,ATTRIBUUT_3,text,MAXIMUM,,REVISED.fme_feature_content,fme_feature_content,OrigFlag,
    QUERY_DEF:
      LATEST_VERSION,SELECT "ENTITEIT_ID",
             "MUTATIE_ID",
             "ATTRIBUUT_1",
             "ATTRIBUUT_2",
             "ATTRIBUUT_3",
             fme_feature_content,
             "Y" as OrigFlag
      FROM ORG
      WHERE DATUM_VERVALLEN IS NULL
      ,FIRST,REVISED,SELECT R."ENTITEIT_ID",
             R."ATTRIBUUT_1",
             R."ATTRIBUUT_2",
             R."ATTRIBUUT_3",
             O.MAXIMUM,
             fme_feature_content,
             "N" as OrigFlag
      FROM REVISED R,
           (SELECT MAX("MUTATIE_ID") AS MAXIMUM FROM ORG) O,FIRST
    LATEST_VERSION -> CoordinateRounder
    REVISED -> CoordinateRounder_2

Bookmark: CoordinateRounders
  Coördinaten afronden op centimeters
CoordinateRounder
    XPREC = 2
    ZPREC = 2
    YPREC = 2
    ROUNDED -> Matcher
    ROUNDED -> ChangeDetector [ORIGINAL]
CoordinateRounder_2
    XPREC = 2
    ZPREC = 2
    YPREC = 2
    ROUNDED -> ChangeDetector [REVISED]
    ROUNDED -> Matcher_2

Bookmark: Mutaties detecteren
ChangeDetector
    MATCH = 2D
    BLANK_AND_MISSING_DIFFER = No
    LENIENT_MATCH = No
    MATCH_STRATEGY = Match Selected Attributes
    EXTRA_VERTEX_TOLERANCE = 0
    MATCHATTRS = ATTRIBUUT_3 ATTRIBUUT_2 ATTRIBUUT_1
    ADDED -> Matcher
    DELETED -> Matcher_2

Bookmark: Matchers & Testers
  Voor iedere bijgewerkte feature twee acties uitvoeren:
  de nieuwe versie van de feature aanmaken (INSERT)
  de oude versie van de feature afsluiten door DATUM_VERVALLEN te vullen (UPDATE)
  Voor iedere verwijderde feature de DATUM_VERVALLEN vullen (INSERT)
Matcher
    MATCH = NONE
    BLANK_AND_MISSING_DIFFER = No
    LENIENT_MATCH = No
    MATCH_STRATEGY = Match Selected Attributes
    MATCHATTRS = ENTITEIT_ID
    DIFFATTRS = OrigFlag
    CNT_ATTR = _match_id
    MATCHED -> TESTER
    NOT_MATCHED -> TESTER_2
TESTER_2: Tester
    BOOL_OP = OR
    TEST_LIST = &OrigFlag,=,N
    TEST_CLAUSE = TEST @Value(OrigFlag) = N
    TEST_DESCRIPTION = ""
    TEST_MODE = Automatic
    PASSED -> AttributeCreator_3
TESTER: Tester
    BOOL_OP = OR
    TEST_LIST = &OrigFlag,=,N
    TEST_CLAUSE = TEST @Value(OrigFlag) = N
    TEST_DESCRIPTION = ""
    TEST_MODE = Automatic
    PASSED -> AttributeCreator_3
    FAILED -> AttributeCreator_8
Matcher_2
    MATCH = NONE
    BLANK_AND_MISSING_DIFFER = No
    LENIENT_MATCH = No
    MATCH_STRATEGY = Match Selected Attributes
    MATCHATTRS = ENTITEIT_ID
    DIFFATTRS = OrigFlag
    CNT_ATTR = _match_id
    NOT_MATCHED -> TESTER_3
TESTER_3: Tester
    BOOL_OP = OR
    TEST_LIST = &OrigFlag,=,Y
    TEST_CLAUSE = TEST @Value(OrigFlag) = Y
    TEST_DESCRIPTION = ""
    TEST_MODE = Automatic
    PASSED -> AttributeCreator_8

Bookmark: Attributen maken
Note: fme_db_operation = INSERT / DATUM_AANGEMAAKT = @Timestamp("^Y^m^d^H^M^S")
AttributeCreator_3
    ATTR_TABLE:
      SET_TO fme_db_operation = INSERT
      SET_TO fme_where
      SET_TO DATUM_AANGEMAAKT = @Timestamp("^Y^m^d^H^M^S")
    -> Counter_2
Note: MUTATIEID aanmaken
Counter_2
    START = FME_CONDITIONAL:DEFAULT_VALUE'1'BOOL_OP;OR;COMPOSITE_TEST;<Unused>;TEST @Value(MAXIMUM) ATTRIBUTE_HAS_VALUE _FME_BLANK_STRING_'@Value(MAXIMUM) + 1'FME_NUM_CONDITIONS2___
    SCOPE = Global
    CNT_ATTR = MUTATIE_ID
    DOMAIN = counter
    -> OBJ.INCLUSIEF_HISTORIE (writer GEODATABASE_SDE_3)
Note: fme_db_operation = UPDATE / fme_where = MUTATIEID = @VALUE(MUTATIEID) / DATUM_VERVALLEN = @Timestamp("^Y^m^d^H^M^S")
AttributeCreator_8
    ATTR_TABLE:
      SET_TO fme_db_operation = UPDATE
      SET_TO fme_where = ENTITEIT_ID = @Value(ENTITEIT_ID)
      SET_TO DATUM_VERVALLEN = @Timestamp("^Y^m^d^H^M^S")
    -> OBJ.INCLUSIEF_HISTORIE (writer GEODATABASE_SDE_3)
