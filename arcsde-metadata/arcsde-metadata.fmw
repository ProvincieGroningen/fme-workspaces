FME workspace arcsde-metadata.fmw
Title: arcsde-attribute-metadata
Description: Workspace om te demonstreren hoe je de metadata van een feature class in ArcSDE kunt wijzigen. Het gaat hierbij om:
- de omschrijving per attribuut
- de revisiedatum
History: 28-8-2018,Willy Tadema,,

Parameters:
- SourceDataset_XLSXR =   # Excel-bestand met attribuutmetadata

Readers:
- XLSXR_1: XLSXR from $(SourceDataset_XLSXR)
- GEODATABASE_SDE_1: GEODATABASE_SDE

Writers:
- GEODATABASE_SDE_2: GEODATABASE_SDE

Bookmark: Metadata van feature class in ArcSDE
Aanlegplaatsen (reader GEODATABASE_SDE_1)
    attributes: fme_feature_identifier char(254), fme_num_entries integer, fme_contains_spatial_column char(3), fme_dimension integer, fme_min_x double, fme_max_x double, fme_min_y double, fme_max_y double
    -> AttributeRenamer
AttributeRenamer
    ATTR_TABLE = RENAME_SET_DEFAULT geodb_metadata_string > geodb_metadata_string_org
    -> XMLUpdater [DOCUMENT]

Bookmark: Naam en omschrijving van attributen
Blad1 (reader XLSXR_1)
    attributes: name char(17), definition char(124)
    -> AttributeCreator

Bookmark: XML path en value bepalen
AttributeCreator
    ATTR_TABLE:
      SET_TO xml_path = //*:featureAttribute[*:name/text() = fme:get-attribute("name")]/*:definition
      SET_TO value = fme:get-attribute("definition")
    -> XMLUpdater [UPDATE]

Bookmark: Updates uitvoeren
XMLUpdater
    OUTPUT_XML_HEADER = Yes
    RESULT_ATTRIBUTE = geodb_metadata_string
    UPDATE_TABLE = GENERATE_QUERY REPLACE_VALUE_WITH_TEXT @Value(xml_path) XML @Value(value)
    VISIBLE_QUERY_VALIDATE = Yes
    XML_TEXT = @Value(geodb_metadata_string_org)
    XML_TYPE = Text or Attribute
    DOCUMENT -> AttributeManager

Bookmark: Nieuwe versie van de metadata wegschrijven naar ArcSDE
AttributeManager
    ATTR_TABLE:
      SET_TO geodb_type = geodb_metadata
      REMOVE geodb_metadata_string_org
      REMOVE fme_feature_identifier
      REMOVE fme_num_entries
      REMOVE fme_contains_spatial_column
      REMOVE fme_dimension
      REMOVE fme_min_x
      REMOVE fme_max_x
      REMOVE fme_min_y
      REMOVE fme_max_y
    -> Aanlegplaatsen (writer GEODATABASE_SDE_2)
Aanlegplaatsen (writer GEODATABASE_SDE_2)
