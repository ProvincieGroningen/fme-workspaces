FME workspace natuurijsbanen.fmw

Parameters:
- DestDataset_ESRISHAPE = ../data/natuurijsbanen.zip   # Destination Esri Shapefile Folder
- QUERY:   # Overpass query
      area["name"="Nederland"]["admin_level"="2"] -> .n;
      (
          node["leisure"="ice_rink"]["seasonal"="yes"](area.n);
          way["leisure"="ice_rink"]["seasonal"="yes"](area.n);
          relation["leisure"="ice_rink"]["seasonal"="yes"](area.n);
      );
      out center;
- XSLT:   # XSL template
      <xsl:stylesheet version="1.0" xmlns:xsl="http://www.w3.org/1999/XSL/Transform" xmlns:msxsl="urn:schemas-microsoft-com:xslt" exclude-result-prefixes="msxsl">
          <xsl:strip-space elements="*"/>
          <xsl:output method="xml" indent="yes"/>
      
          <xsl:template match="@* | node()">
              <xsl:copy>
                  <xsl:apply-templates select="@* | node()"/>
              </xsl:copy>
          </xsl:template>
      
          <xsl:template match="node">
               <xsl:element name="poi">
                  <xsl:element name="objectid">
                      <xsl:value-of select="@id"/>
                  </xsl:element>
                  <objecttype>node</objecttype>
                  <xsl:element name="lat">
                      <xsl:value-of select="@lat"/>
                  </xsl:element>
                  <xsl:element name="lon">
                      <xsl:value-of select="@lon"/>
                  </xsl:element>
                  <xsl:for-each select="tag">
                      <xsl:element name="{translate(@k, ':', '')}">
                          <xsl:value-of select="@v"/>
                      </xsl:element>
                  </xsl:for-each>
              </xsl:element>
          </xsl:template>
      
          <xsl:template match="way">
              <xsl:element name="poi">
                  <xsl:element name="objectid">
                      <xsl:value-of select="@id"/>
                  </xsl:element>
                  <objecttype>way</objecttype>
                  <xsl:element name="lat">
                      <xsl:value-of select="center/@lat"/>
                  </xsl:element>
                  <xsl:element name="lon">
                      <xsl:value-of select="center/@lon"/>
                  </xsl:element>
                  <xsl:for-each select="tag">
                      <xsl:element name="{translate(@k, ':', '')}">
                          <xsl:value-of select="@v"/>
                      </xsl:element>
                  </xsl:for-each>
              </xsl:element>
      
          </xsl:template>
              <xsl:template match="relation">
              <xsl:element name="poi">
                  <xsl:element name="objectid">
                      <xsl:value-of select="@id"/>
                  </xsl:element>
                  <objecttype>relation</objecttype>
                  <xsl:element name="lat">
                      <xsl:value-of select="center/@lat"/>
                  </xsl:element>
                  <xsl:element name="lon">
                      <xsl:value-of select="center/@lon"/>
                  </xsl:element>
                  <xsl:for-each select="tag">
                      <xsl:element name="{translate(@k, ':', '')}">
                          <xsl:value-of select="@v"/>
                      </xsl:element>
                  </xsl:for-each>
              </xsl:element>
          </xsl:template>
      
      </xsl:stylesheet>

Writers:
- ESRISHAPE_1: ESRISHAPE to $(DestDataset_ESRISHAPE) in EPSG:3857

Note: Deze workspace vraagt natuurijsbanen op uit OpenStreetMap. Daarbij wordt gebruikt gemaakt van de Overpass API. / Bekijk de Github repository https://github.com/FrieseWoudloper/workshop-maptime2016-overpass voor meer uitleg over de Overpass Query Language (QL). / Deze workspace haalt alleen natuurijsbanen op die: / - zijn ingetekend als node, way of relation, / - zijn getagt met de key-value pairs "leisure"="ice_rink" en "seasonal"="yes", / - liggen binnen de landsgrenzen van Nederland. / Met dank aan Pim Verver voor zijn uitleg over de HTTPCaller en XSLTProcessor transformers: http://gis.travelingo.nl/2016/07/06/fme-en-de-overpass-api-van-openstreetmap/
Creator
    GEOMTYPE = Geometry Object
    NUM = 1
    CREATED -> HTTPCaller
Note: Overpass API request
HTTPCaller
    USE_COOKIES = No
    STATUS_CODE_ATTR = _http_status_code
    TARGET_URL = http://overpass-api.de/api/interpreter?
    TARGET_ATTR = _response_body
    HTTP_METHOD = GET
    VERIFY_SSL_CERTIFICATES = Yes
    SAVE_FILE = Attribute
    TARGET_ATTR_ENCODING = auto-detect
    TRANSFER_TIMEOUT_LENGTH = 90
    CONNECTION_TIMEOUT_LENGTH = 60
    RESPONSE_HEADER_LIST_ATTR = _headers
    ADDITIONAL_URL_PARAMETERS = data;$(QUERY)
    FOLLOW_REDIRECTS = Yes
    ERROR_ATTR = _error
    -> XSLTProcessor
Note: Transformeren van de API response zodat het verder verwerkt kan worden
XSLTProcessor
    CONFIGURATION_TYPE = Embedded Stylesheet
    EMBEDDED_STYLESHEET = $(XSLT)
    ATTRIBUTE_XML = _response_body
    ATTRIBUTE_RESULTS = _result
    RESULTS_TYPE = Results in Attribute
    XML_INPUT_TYPE = Attribute with XML Document
    TRANSFORMED -> XMLFragmenter
Note: Alleen objectid, objecttype, name, operator, website, lat en lon worden nu 'exposed'. / Dit lijstje kun je natuurlijk uitbreiden.
XMLFragmenter
    MERGE_ATTRS = No
    ATTRIBUTE_XML = _result
    NEW_ATTRIBUTES = objectid objecttype name operator website lat lon
    FEATURE_TYPES_FORMAT_NAME = XML
    XML_SOURCE_TYPE = Attribute with XML document
    EMBEDDED_EXPRESSIONS = osm/poi
    FLATTEN_OPTIONS = <structure separator="." map-empty-elements="yes" matched-prefix="attributes" matched-attributes="yes" cardinality="+{?}" structure-prefix="" child-position-attribute="" except-expression="" ui-mode="basic" matched-ancestor-attributes=""/>
    FRAGMENTS -> VertexCreator
VertexCreator
    MODE_NAME = Add Point
    YVAL = @Value(lat)
    XVAL = @Value(lon)
    -> CoordinateSystemSetter
CoordinateSystemSetter
    COORDSYS = EPSG:4326
    -> AttributeManager
AttributeManager
    ATTR_TABLE:
      RENAME_SET_VALUE name > naam
      REMOVE lat
      REMOVE lon
      REMOVE xml_fragment
      REMOVE xml_id
      REMOVE xml_matched_element
      REMOVE xml_parent_id
      REMOVE xml_parent_child_pos
      SET_TO osmlink = FME_CONDITIONAL:DEFAULT_VALUE'_FME_NO_OP_'BOOL_OP;OR;COMPOSITE_TEST;<Unused>;TEST @Value(objecttype) = node'https://www.openstreetmap.org/node/@Value(objectid)'BOOL_OP;OR;COMPOSITE_TEST;<Unused>;TEST @Value(objecttype) = way'https://www.openstreetmap.org/way/@Value(objectid)'BOOL_OP;OR;COMPOSITE_TEST;<Unused>;TEST @Value(objecttype) = relation'https://www.openstreetmap.org/relation/@Value(objectid)'FME_NUM_CONDITIONS4___
    -> natuurijsbanen (writer ESRISHAPE_1)
natuurijsbanen (writer ESRISHAPE_1)
    attributes: objectid char(200), objecttype char(200), naam char(200), operator char(200), website char(200), osmlink char(200)
