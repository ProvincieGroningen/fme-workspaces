FME workspace verkeersbesluiten.fmw

Parameters:
- MaxAantalRecords = 1000   # Maximum aantal records in reponse
- Query = (keyword=verkeersbesluit) and (creator=groningen) and (organisationType=Provincie)

Note: Auteur: Willy Tadema / Datum: 18 februari 2018 / Omschrijving: / Workspace om te demonstreren hoe je verkeersbesluiten die gepubliceerd zijn in de Staatscourant op kunt te vragen. De besluiten die voorzien zijn van coördinaten worden op een kaart geplot. / Published parameters: / MaxAantalRecords - het maximum aantal records dat de webservice van Overheid.nl retourneert / Query - het filter dat binnen de collectie Officiële Publicaties toegepast moet worden om de verkeersbesluiten te selecteren van een specifieke overheidsorganisatie
Creator
    NUM = 1
    GEOMTYPE = Geometry Object
    CREATED -> HTTPCaller
HTTPCaller
    RESPONSE_HEADER_LIST_ATTR = _headers
    FOLLOW_REDIRECTS = Yes
    TARGET_URL = http://zoekdienst.overheid.nl/sru/Search?
    VERIFY_SSL_CERTIFICATES = Yes
    ERROR_ATTR = _error
    TARGET_ATTR_ENCODING = auto-detect
    TRANSFER_TIMEOUT_LENGTH = 90
    STATUS_CODE_ATTR = _http_status_code
    SAVE_FILE = Attribute
    FILE_TYPE = <Auto Detect from HTTP Headers>
    CONNECTION_TIMEOUT_LENGTH = 60
    HTTP_METHOD = GET
    ADDITIONAL_URL_PARAMETERS = version;1.2 operation;searchRetrieve x-connection;oep startRecord;1 maximumRecords;$(MaxAantalRecords) query;$(Query)
    USE_COOKIES = No
    TARGET_ATTR = _response_body
    -> XSLTProcessor
    -> XMLXQueryExtractor
Note: Transformeren van de API response m.b.v. een XSL style sheet
XSLTProcessor
    XML_INPUT_TYPE = Attribute with XML Document
    EMBEDDED_STYLESHEET:
      <xsl:stylesheet version="1.0"
          xmlns:xsl="http://www.w3.org/1999/XSL/Transform"
          xmlns:srw="http://www.loc.gov/zing/srw/"
          xmlns:sru="http://standaarden.overheid.nl/sru"
          xmlns:dcterms="http://purl.org/dc/terms/"
          xmlns:overheid="http://standaarden.overheid.nl/owms/terms/"
          xmlns:overheidop="http://standaarden.overheid.nl/product/terms/"
          xmlns:overheidvb="http://standaarden.overheid.nl/vb/terms">

        <xsl:strip-space elements="*"/>
        <xsl:output method="xml" indent="yes"/>

        <xsl:template match="@*|node()">
          <xsl:apply-templates select="@*|node()"/>
        </xsl:template>

        <xsl:template match="srw:searchRetrieveResponse">
          <verkeersbesluiten>
            <xsl:apply-templates/>
          </verkeersbesluiten>
        </xsl:template>

        <xsl:template match="sru:gzd">
          <verkeersbesluit>
            <xsl:apply-templates/>
          </verkeersbesluit>
        </xsl:template>

        <xsl:template match="overheidop:owmskern">
          <titel1><xsl:value-of select="dcterms:title"/></titel1>
          <locatie><xsl:value-of select="dcterms:spatial"/></locatie>
        </xsl:template>

        <xsl:template match="overheidop:owmsmantel">
          <titel2><xsl:value-of select="dcterms:alternative"/></titel2>
        </xsl:template>

        <xsl:template match="sru:enrichedData">
          <url><xsl:value-of select="sru:url"/></url>
        </xsl:template>

      </xsl:stylesheet>
    ATTRIBUTE_XML = _response_body
    CONFIGURATION_TYPE = Embedded Stylesheet
    RESULTS_TYPE = Results in Attribute
    ATTRIBUTE_RESULTS = _result
    TRANSFORMED -> XMLFragmenter
XMLFragmenter
    EMBEDDED_EXPRESSIONS = verkeersbesluiten/verkeersbesluit
    NEW_ATTRIBUTES = titel1 titel2 locatie url
    ATTRIBUTE_XML = _result
    FEATURE_TYPES_FORMAT_NAME = XML
    XML_SOURCE_TYPE = Attribute with XML document
    MERGE_ATTRS = No
    FLATTEN_OPTIONS = <structure separator="." map-empty-elements="yes" matched-prefix="attributes" matched-attributes="yes" cardinality="+{?}" structure-prefix="" child-position-attribute="" except-expression="" ui-mode="basic" matched-ancestor-attributes=""/>
    FRAGMENTS -> AttributeCreator
GeometryReplacer
    SOURCE = @Value(wkt)
    REMOVE_ATTRIBUTE = No
    KIND_LONG = OGC Well Known Text
    OGC_WKT_PRECISION_DISPLAY = 64-bit
    -> AttributeRemover
AttributeRemover
    REMOVE_ATTRS = wkt,locatie_preprocessed
    -> Verkeersbesluiten
Verkeersbesluiten: Inspector
Note: Selecteren van attribuutwaarde m.b.v. XQuery
XMLXQueryExtractor
    QUERY_EXPR:
      declare namespace srw="http://www.loc.gov/zing/srw/";
      //srw:numberOfRecords/text()
    XQUERY_TYPE = XQuery expression
    WRITE_XML_HEADER = No
    XML_TYPE = Attribute specifying XML
    XML_ATTR = _response_body
    XML_REMOVE_SOURCE_ATTR = No
    RESULT_TYPE_NAME = Single value
    RESULT_ATTRIBUTE = AantalRecords
    QUERY_RESULTS -> Tester
Tester
    TEST_MODE = Automatic
    TEST_CLAUSE = TEST @Value(AantalRecords) > $(MaxAantalRecords)
    TEST_DESCRIPTION = ""
    BOOL_OP = OR
    PASSED -> MessageLogger
Note: Geef een waarschuwing als het aantal besluiten / gelijk is aan het maximum aantal
MessageLogger
    TYPE = WARN
    MAXFEATS = 20
    __MESSAGELOGGER_LOGMESSAGE = Let op: Niet alle records die voldoen aan het query-filter worden geretourneerd! Alleen de eerste $(MaxAantalRecords).
    LOGFEATS = No
    MAXCOORDS = 20

Bookmark: Transformatie geometrie naar WKT
AttributeCreator
    ATTR_TABLE = SET_TO locatie_preprocessed = @Trim(@ReplaceRegEx(@Value(locatie),[^(0-9{6}|\s|\$%\$)],""))
    -> StringReplacer
StringReplacer
    SRC_ATTRS = locatie_preprocessed
    REGEXP = YES
    FIND_TEXT = (\$%\$){1,}$
    NO_MATCH = _FME_NO_OP_
    CASE = NO
    -> AttributeManager
AttributeManager
    ATTR_TABLE:
      REMOVE xml_fragment
      REMOVE xml_id
      REMOVE xml_matched_element
      REMOVE xml_parent_id
      REMOVE xml_parent_child_pos
      SET_TO wkt = FME_CONDITIONAL:DEFAULT_VALUE'_FME_NO_OP_'BOOL_OP;OR;COMPOSITE_TEST;<Unused>;TEST @Evaluate(@StringLength(@Value(locatie_preprocessed))) = 13'POINT(@ReplaceString(@Value(locatie_preprocessed),"%$%",","))'BOOL_OP;OR;COMPOSITE_TEST;<Unused>;TEST @Evaluate(@StringLength(@Value(locatie_preprocessed))) > 13'LINESTRING(@ReplaceString(@Value(locatie_preprocessed),"$%$",","))'FME_NUM_CONDITIONS3___
    -> GeometryReplacer
